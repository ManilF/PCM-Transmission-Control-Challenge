# Transmission_Requirements

## #1: Gear Selection Safety (Functional)
| The transmission controller shall permit gear selection only when operating conditions are valid for the requested gear. |
| --- |

### #2: Park Engagement (Functional)
| The transmission controller shall permit engagement of PARK only when \|vehSpd\| < 0.1 m/s |
| --- |

### GS-01: Valid Gears Only (Functional)
The manager shall command gears 1-10 only in Drive, 0 in Neutral/Park, and -1 in Reverse. Invalid candidates shall never pass.

### RP-01: Drive Request Speed Protection (Functional)
The transmission controller shall accept a Drive request only when signed vehicle speed is strictly greater than −0.5 m/s. When Drive is requested at or below −0.5 m/s, the accepted range shall be Neutral.

### RP-02: Reverse Request Speed Protection (Functional)
The transmission controller shall accept a Reverse request only when signed vehicle speed is strictly less than 0.5 m/s. When Reverse is requested at or above 0.5 m/s, the accepted range shall be Neutral.

### GS-04: 1-second Shift Timer (Functional)
Upon receiving a new gear command from the controller, all further commands within a 1 second time window will be ignored.

### RP-03: Neutral Request Handling (Functional)
The controller shall accept Neutral at any vehicle speed and set the accepted range to Neutral when a Drive, Reverse, or Park request is rejected.

### RP-04: Parking Actuator Response (Functional)
For a valid Park request, the controller shall command the parking actuator closed within 100 ms and release it within 100 ms of leaving Park.

## #3: Engine Operating Limits (Functional)
| The transmission controller shall prevent operation of the engine outside its allowable operating range. |
| --- |

### GS-03: Maximum Engine Speed (Functional)
| The transmission controller shall prevent engine speed from exceeding 7250 RPM. If engine speed exceeds 7250 RPM, request upshift to protect engine. |
| --- |
- Rationale: Higher engine speeds will cause the internal piston forces to excess material limitations.

## #9: Driver Request Handling (Functional)
| The transmission controller shall process driver gear requests according to transmission operating constraints. |
| --- |

### #10: Park Request Protection (Functional)
The transmission controller shall always command neutral when park is selected
- Rationale: If the transmission is in any drive or reverse gears it will cause undue strain on the engine and torque converter.

## #11: Vehicle Performance (Functional)
The vehicle shall accelerate from 0 to 60 mph in less than 12 seconds when wide-open-throttle is applied (100% throttle)
- Rationale: If 0-60 acceleration time is greater than 12 seconds it will create unsafe situations on the road during merging and other high-acceleration manoeuvers.

### PE-01: Driver-demand-sensitive upshift decision (Functional)
While Drive is accepted and the current commanded forward gear is 1 through 9, the Performance and Efficiency Planner shall request an ordinary upshift when engine speed is at or above the calibrated demand-dependent threshold, and shall not request it below that threshold. For the current calibration, the threshold is 4500 RPM plus 1500 RPM multiplied by driver throttle limited to the interval 0 to 1, for every gear 1 through 9. The Planner shall not request an ordinary upshift outside accepted Drive or at gear 10. Higher-priority Gear Safety decisions shall retain authority over the final gear command.
- Rationale: At the same gear and engine speed, low demand permits an earlier upshift while high demand retains the lower gear longer

### PE-02: Prevent an ordinary shift reversal after a confirmed forward shift (Functional)
After a confirmed forward shift, the planner shall block opposite-direction proposals for at least two controller periods. Repeated proposals shall not restart the hold; leaving Drive shall cancel it.
